-- PARKS-CPUMEM-STATS-MIB
-- version 1.0.0
-- PARKS Comunicacoes Digitais
-- Copyright 2006 by PARKS Comunicacoes Digitais. All Rights Reserved.
-- This PARKS SNMP MIB Specification is PARKS proprietary intellectual 
-- property.
-- This module will be extend, as required. The specification and other
-- information 
-- contained in this document can be modified without prior notice. The 
-- user should consult PARKS to determine whether any such changes have 
-- been done.
--
-- MODULE-IDENTITY
--	ORGANIZATION "PARKS Comunicacoes Digitais"
--	CONTACT-INFO 
--		     "PARKS Comunicacoes Digitais
--	
--                    Postal: PARKS Comunicacoes Digitais
--                    Cruzeiro 530
--                    Distrito Industrial, Cachoeirinha, RS
--                    CEP 94930-615 
--                    BRAZIL
--
--                    E-mail: suporte@parks.com.br "
--
--      DESCRIPTION
--                    " The Structure of Management Information for 
--                      PARKS Comunicacoes Digitais enterprise. "

PARKS-CPUMEM-STATS-MIB	DEFINITIONS ::= BEGIN
	IMPORTS
		DisplayString
			FROM SNMPv2-TC
		parksCPUMemStats
			FROM PARKS-STATISTICS-MIB
		OBJECT-TYPE, Counter, mib-2, enterprises, Integer32, Counter32
			FROM SNMPv2-SMI;

	pkCPUStats	OBJECT IDENTIFIER
		::=  {  parksCPUMemStats  1  }

	pkMemoryStats	OBJECT IDENTIFIER
		::=  {  parksCPUMemStats  2  }

	pkCPUIdle	OBJECT-TYPE	
		SYNTAX			Integer32
		MAX-ACCESS		read-only
		STATUS			current
		DESCRIPTION		"Per mille of idle CPU time."
		::=  {  pkCPUStats  1  }

	pkCpuSystem	OBJECT-TYPE	
		SYNTAX			Integer32
		MAX-ACCESS		read-only
		STATUS			current
		DESCRIPTION		"Per mille of system CPU time."
		::=  {  pkCPUStats  2  }

	pkCpuChipset	OBJECT-TYPE	
		SYNTAX			DisplayString  ( SIZE ( 0 .. 255  ) ) 
		MAX-ACCESS		read-only
		STATUS			current
		DESCRIPTION		"Chipset of the CPU."
		::=  {  pkCPUStats  3  }

	pkCpuMachine	OBJECT-TYPE	
		SYNTAX			DisplayString  ( SIZE ( 0 .. 255  ) ) 
		MAX-ACCESS		read-only
		STATUS			current
		DESCRIPTION		"Description of the equipment."
		::=  {  pkCPUStats  4  }

	pkCpuCoreClk	OBJECT-TYPE	
		SYNTAX			Integer32
		MAX-ACCESS		read-only
		STATUS			current
		DESCRIPTION		"Core Clock of the CPU in MHz."
		::=  {  pkCPUStats  5  }

	pkCpuBusClk	OBJECT-TYPE	
		SYNTAX			Integer32
		MAX-ACCESS		read-only
		STATUS			current
		DESCRIPTION		"Bus Clock of the CPU in MHz."
		::=  {  pkCPUStats  6  }

	pkMemoryTotal	OBJECT-TYPE	
		SYNTAX			Counter32
		MAX-ACCESS		read-only
		STATUS			current
		DESCRIPTION		"Total Memory size on the host. Minus kernel anda data space, in Kb"
		::=  {  pkMemoryStats  1  }

	pkMemoryFree	OBJECT-TYPE	
		SYNTAX			Counter32
		MAX-ACCESS		read-only
		STATUS			current
		DESCRIPTION		"Total available Memory on the host, in Kb."
		::=  {  pkMemoryStats  2  }

	pkMemoryUsed	OBJECT-TYPE	
		SYNTAX			Counter32
		MAX-ACCESS		read-only
		STATUS			current
		DESCRIPTION		"Total used memory on the host, in Kb."
		::=  {  pkMemoryStats  3  }

END
