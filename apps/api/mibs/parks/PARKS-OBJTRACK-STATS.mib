-- PARKS-OBJTRACK-STATS-MIB
-- version 1.0.0
-- PARKS Comunicacoes Digitais
-- Copyright 2011 by PARKS Comunicacoes Digitais. All Rights Reserved.
-- This PARKS SNMP MIB Specification is PARKS proprietary intellectual
-- property.
-- This module will be extend, as required. The specification and other
-- information contained in this document can be modified without
-- prior notice. The user should consult PARKS to determine whether any
-- such changes have been done.
--
-- MODULE-IDENTITY
--	ORGANIZATION "PARKS Comunicacoes Digitais"
--	CONTACT-INFO
--			 "Postal: PARKS Comunicacoes Digitais
--			  Cruzeiro 530 ,  Distrito Industrial,
--			  CEP 94930-615   Cachoeirinha, RS, BRAZIL
--			  E-mail: suporte@parks.com.br "
--
--      DESCRIPTION
--                    " MIB for Object Tracking status in Parks devices. "

PARKS-OBJTRACK-STATS-MIB	DEFINITIONS ::= BEGIN
	IMPORTS
		RowStatus, TEXTUAL-CONVENTION, TruthValue, DisplayString
			FROM SNMPv2-TC
		OBJECT-TYPE, Counter, TimeTicks, mib-2, enterprises, Integer32, Counter32
			FROM SNMPv2-SMI
		parksObjTrackStats
			FROM PARKS-STATISTICS-MIB;

	pkObjTrackStats OBJECT IDENTIFIER
		::=  {  parksObjTrackStats  1  }

	pkObjTrackSensorStats OBJECT IDENTIFIER
		::=  {  parksObjTrackStats  2  }

	pkObjTrackTraps OBJECT IDENTIFIER
		::=  {  parksObjTrackStats  3  }

--
	ObjTrackSensorType ::= TEXTUAL-CONVENTION
		STATUS       current
		DESCRIPTION 	"This data type is used as the syntax of the
			pkObjTrackSensorStatsType object in the definition of
			pkObjTrackSensorStatsTable table.

			The definition of this textual convention with the
			addition of newly assigned values is published by PARKS
			as needed."
		SYNTAX  INTEGER {
				interface(1),
				icmpEcho(2),
				ipsecTunnel(3),
				gsmIface(4),
				adslIface(5),
				listBoolean(6)
				}

--
	pkObjTrackStatsTable	OBJECT-TYPE
		SYNTAX		SEQUENCE  OF  PkObjTrackStatsEntry
		MAX-ACCESS	not-accessible
		STATUS		current
		DESCRIPTION	"Table containing the current status for each
		                 Track"
		::=  { pkObjTrackStats  1 }

	pkObjTrackStatsEntry	OBJECT-TYPE
		SYNTAX		PkObjTrackStatsEntry
		MAX-ACCESS	not-accessible
		STATUS		current
		DESCRIPTION	"List of current status for each track"
		INDEX		{  pkObjTrackStatsIndex  }
		::=  { pkObjTrackStatsTable 1 }

	PkObjTrackStatsEntry  ::=  SEQUENCE {
		pkObjTrackStatsIndex		INTEGER,
		pkObjTrackStatsStatus		INTEGER,
		pkObjTrackStatsLastChange	TimeTicks,
		pkObjTrackStatsEvents		Counter32
		}

	pkObjTrackStatsIndex OBJECT-TYPE
		SYNTAX		INTEGER
		MAX-ACCESS	read-only
		STATUS		current
		DESCRIPTION	"A unique value identifying each Track"
		::= { pkObjTrackStatsEntry 1 }

	pkObjTrackStatsStatus OBJECT-TYPE
		SYNTAX		INTEGER {
					up(1),
					down(2),
					testing(3)
				}
		MAX-ACCESS	read-only
		STATUS		current
		DESCRIPTION	"The current operational state of each Track. The
			testing(3) state indicates that some sort of debugging has
			been activated by the user and the actual state of the
			track is unknown."
		::= { pkObjTrackStatsEntry 2 }

	pkObjTrackStatsLastChange OBJECT-TYPE
		SYNTAX		TimeTicks
		MAX-ACCESS	read-only
		STATUS		current
		DESCRIPTION	"The value of sysUpTime at the time the track
			entered its current operational state."
		::= { pkObjTrackStatsEntry 3 }

	pkObjTrackStatsEvents OBJECT-TYPE
		SYNTAX		Counter32
		MAX-ACCESS	read-only
		STATUS		current
		DESCRIPTION	"Total number of operational state changes.
			Discontinuities in the value of this counter can occur at
			re-initialization of the management system."
		::= { pkObjTrackStatsEntry 4 }

--
	pkObjTrackSensorStatsTable	OBJECT-TYPE
		SYNTAX		SEQUENCE  OF  PkObjTrackSensorStatsEntry
		MAX-ACCESS	not-accessible
		STATUS		current
		DESCRIPTION	"Table containing the current status for each
		                 Track"
		::=  { pkObjTrackSensorStats  1 }

	pkObjTrackSensorStatsEntry	OBJECT-TYPE
		SYNTAX		PkObjTrackSensorStatsEntry
		MAX-ACCESS	not-accessible
		STATUS		current
		DESCRIPTION	"List of current status for each track"
		INDEX		{  pkObjTrackStatsIndex, pkObjTrackSensorStatsIndex  }
		::=  { pkObjTrackSensorStatsTable 1 }

	PkObjTrackSensorStatsEntry  ::=  SEQUENCE {
		pkObjTrackSensorStatsIndex		INTEGER,
		pkObjTrackSensorStatsType		ObjTrackSensorType,
		pkObjTrackSensorStatsStatus		INTEGER,
		pkObjTrackSensorStatsLastChange		TimeTicks,
		pkObjTrackSensorStatsEvents		Counter32
		}

	pkObjTrackSensorStatsIndex OBJECT-TYPE
		SYNTAX		INTEGER
		MAX-ACCESS	read-only
		STATUS		current
		DESCRIPTION	"A unique value identifying each sensor in a track"
		::= { pkObjTrackSensorStatsEntry 1 }

	pkObjTrackSensorStatsType OBJECT-TYPE
		SYNTAX		ObjTrackSensorType
		MAX-ACCESS	read-only
		STATUS		current
		DESCRIPTION	"The type of the sensor. Additional values for
			pkObjTrackSensorStatsType are assigned by PARKS,
			through updating the syntax of the ObjTrackSensorType
			textual convention."
		::= { pkObjTrackSensorStatsEntry 2 }

	pkObjTrackSensorStatsStatus OBJECT-TYPE
		SYNTAX		INTEGER {
					up(1),
					down(2)
				}
		MAX-ACCESS	read-only
		STATUS		current
		DESCRIPTION	"The current operational state of the sensor."
		::= { pkObjTrackSensorStatsEntry 3 }

	pkObjTrackSensorStatsLastChange OBJECT-TYPE
		SYNTAX		TimeTicks
		MAX-ACCESS	read-only
		STATUS		current
		DESCRIPTION	"The value of sysUpTime at the time the sensor
			entered its current operational state."
		::= { pkObjTrackSensorStatsEntry 4 }

	pkObjTrackSensorStatsEvents OBJECT-TYPE
		SYNTAX		Counter32
		MAX-ACCESS	read-only
		STATUS		current
		DESCRIPTION	"Total number of operational state changes.
			Discontinuities in the value of this counter can occur at
			re-initialization of the management system."
		::= { pkObjTrackSensorStatsEntry 5 }

--
pkObjTrackTrapsStats 	OBJECT-IDENTITY
	STATUS		current
	DESCRIPTION	"Traps for Object Tracking mib."
		::=  { pkObjTrackTraps 1 }

	pkObjTrackStatusTrap 	NOTIFICATION-TYPE
		OBJECTS	{ pkObjTrackStatsIndex , pkObjTrackStatsStatus }
		STATUS		current
		DESCRIPTION	"Indicates a change in the state of the track"
		::=  { pkObjTrackTrapsStats	1 }
		

END
