-- PARKS-DHCPL2RELAY-MIB
-- version 1.1.0
-- PARKS Comunicacoes Digitais
-- Copyright 2011 by PARKS Comunicacoes Digitais. All Rights Reserved.
-- This PARKS SNMP MIB Specification is PARKS proprietary intellectual 
-- property.
-- This module will be extend, as required. The specification and other
-- information 
-- contained in this document can be modified without prior notice. The 
-- user should consult PARKS to determine whether any such changes have 
-- been done.
--
-- MODULE-IDENTITY
--	ORGANIZATION "PARKS Comunicacoes Digitais"
--	CONTACT-INFO 
--                   		 "Postal: PARKS Comunicacoes Digitais
--                   		              Cruzeiro 530 ,  Distrito Industrial,
--                    		             CEP 94930-615   Cachoeirinha, RS, BRAZIL
-- 	                             E-mail: suporte@parks.com.br "
--
--      DESCRIPTION
--                    " MIB with configuration for DHCP Layer-2 Relay Agent in PARKS devices. "

PARKS-DHCPL2RELAY-MIB		DEFINITIONS ::= BEGIN
	IMPORTS
		DisplayString
			FROM SNMPv2-TC
		OBJECT-TYPE, enterprises, Integer32
			FROM SNMPv2-SMI
		parksDhcpL2Relay
			FROM PARKS-FEATURES-MIB;
	
	pkDhcpL2RelayAccessNode	OBJECT-TYPE
		SYNTAX			DisplayString (SIZE (0..63))
		MAX-ACCESS		read-write
		STATUS			current
		DESCRIPTION		"Equipment's Access Node Identifier"
		::=  { parksDhcpL2Relay 1 }
	
	pkDhcpL2RelayResetAccessNode	OBJECT-TYPE
		SYNTAX			INTEGER	{ yes(1), no(2) }
		MAX-ACCESS		read-write
		STATUS			current
		DESCRIPTION		"Reset Equipment's Access Node Identifier to default"
		::=  { parksDhcpL2Relay 2 }
	
	pkDhcpL2RelayIfTable	OBJECT-TYPE
		SYNTAX			SEQUENCE OF PkDhcpL2RelayIfEntry
		MAX-ACCESS		not-accessible
		STATUS			current
		DESCRIPTION		"DHCP L2 Realy Agent interface table."
		::= { parksDhcpL2Relay 3 }
	
		pkDhcpL2RelayIfEntry	OBJECT-TYPE
			SYNTAX			PkDhcpL2RelayIfEntry
			MAX-ACCESS		not-accessible
			STATUS			current
			DESCRIPTION		"DHCP L2 Realy Agent entries."
			INDEX			{ pkDhcpL2RelayIfIndex }
			::= { pkDhcpL2RelayIfTable 1 }
		
		PkDhcpL2RelayIfEntry ::=	SEQUENCE {
			pkDhcpL2RelayIfIndex		INTEGER,
			pkDhcpL2RelayIfName			DisplayString,
			pkDhcpL2RelayIfStatus		INTEGER,
			pkDhcpL2RelayRemoteId		DisplayString,
			pkDhcpL2RelayResetRemoteId	INTEGER
		}
		
			pkDhcpL2RelayIfIndex	OBJECT-TYPE
				SYNTAX			INTEGER
				MAX-ACCESS		read-only
				STATUS			current
				DESCRIPTION		"Index of each interface, its constant until destruction of
								an interface or reset of the equipment. "
				::= { pkDhcpL2RelayIfEntry 1 }
			
			pkDhcpL2RelayIfName		OBJECT-TYPE
				SYNTAX			DisplayString (SIZE (0..255))
				MAX-ACCESS		read-only
				STATUS			current
				DESCRIPTION		"Name of the interface."
				::= { pkDhcpL2RelayIfEntry 2 }
			
			pkDhcpL2RelayIfStatus	OBJECT-TYPE
				SYNTAX			INTEGER	{ disable(1), untrust(2), trust(3), server(4) }
				MAX-ACCESS		read-write
				STATUS			current
				DESCRIPTION		"Interface's DHCP characteristics"
				::= { pkDhcpL2RelayIfEntry 3 }
				
			pkDhcpL2RelayRemoteId	OBJECT-TYPE
				SYNTAX			DisplayString (SIZE (0..63))
				MAX-ACCESS		read-write
				STATUS			current
				DESCRIPTION		"Interface's Remote Identifier"
				::=  { pkDhcpL2RelayIfEntry 4 }
				
			pkDhcpL2RelayResetRemoteId	OBJECT-TYPE
				SYNTAX			INTEGER	{ yes(1), no(2) }
				MAX-ACCESS		read-write
				STATUS			current
				DESCRIPTION		"Reset interface's Remote Identifier to default"
				::=  { pkDhcpL2RelayIfEntry 5 }
		
	pkDhcpL2RelayStatistics	OBJECT IDENTIFIER
		::=  { parksDhcpL2Relay 4 }
		
		pkDhcpL2RelayResetStats	OBJECT-TYPE
			SYNTAX			INTEGER	{ yes(1), no(2) }
			MAX-ACCESS		read-write
			STATUS			current
			DESCRIPTION		"Reset Statistic counters for DHCP L2 Relay Agent"
			::=  { pkDhcpL2RelayStatistics 1 }
		
		pkDhcpL2RelayClientStats	OBJECT IDENTIFIER
			::=  { pkDhcpL2RelayStatistics 2 }
			
			pkDhcpL2RelayClientsOkPackets	OBJECT-TYPE
				SYNTAX			Integer32
				MAX-ACCESS		read-only
				STATUS			current
				DESCRIPTION		"Good packets received from clients"
				::=  { pkDhcpL2RelayClientStats 1 }
			
			pkDhcpL2RelayClientsBogusPackets	OBJECT-TYPE
				SYNTAX			Integer32
				MAX-ACCESS		read-only
				STATUS			current
				DESCRIPTION		"Bogus packets received from servers"
				::=  { pkDhcpL2RelayClientStats 2 }
		
		pkDhcpL2RelayServerStats	OBJECT IDENTIFIER
			::=  { pkDhcpL2RelayStatistics 3 }
			
			pkDhcpL2RelayServersOkPackets	OBJECT-TYPE
				SYNTAX			Integer32
				MAX-ACCESS		read-only
				STATUS			current
				DESCRIPTION		"Good packets received from clients"
				::=  { pkDhcpL2RelayServerStats 1 }
			
			pkDhcpL2RelayServersBogusPackets	OBJECT-TYPE
				SYNTAX			Integer32
				MAX-ACCESS		read-only
				STATUS			current
				DESCRIPTION		"Bogus packets received from servers"
				::=  { pkDhcpL2RelayServerStats 2 }
		
		pkDhcpL2RelayGenErrors	OBJECT IDENTIFIER
			::=  { pkDhcpL2RelayStatistics 4 }
			
			pkDhcpL2RelayErrorBogusGiaddr	OBJECT-TYPE
				SYNTAX			Integer32
				MAX-ACCESS		read-only
				STATUS			current
				DESCRIPTION		"Packets received from servers with bogus giaddr"
				::=  { pkDhcpL2RelayGenErrors 1 }
			
			pkDhcpL2RelayErrorMissCircId	OBJECT-TYPE
				SYNTAX			Integer32
				MAX-ACCESS		read-only
				STATUS			current
				DESCRIPTION		"Received packets without Circuit-ID on Information Option"
				::=  { pkDhcpL2RelayGenErrors 2 }
			
			pkDhcpL2RelayErrorRxedInformation	OBJECT-TYPE
				SYNTAX			Integer32
				MAX-ACCESS		read-only
				STATUS			current
				DESCRIPTION		"Received packets from clients with Information Option"
				::=  { pkDhcpL2RelayGenErrors 3 }
	
END
